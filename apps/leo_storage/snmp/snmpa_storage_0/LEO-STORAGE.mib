LEO-STORAGE DEFINITIONS ::= BEGIN

IMPORTS
        MODULE-IDENTITY, OBJECT-TYPE, Gauge32, enterprises FROM SNMPv2-SMI

        OBJECT-GROUP FROM SNMPv2-CONF

        DisplayString, TruthValue FROM SNMPv2-TC;

        leofs    MODULE-IDENTITY
                 LAST-UPDATED "201803220000Z"
                 ORGANIZATION "github.com/leo-project"
                 CONTACT-INFO
                             "e-mail:dev@leo-project.org"
                 DESCRIPTION
                             "LEO STORAGE SNMP MIB"
                 REVISION    "v1.4.0"
                 DESCRIPTION
                             "v1.4.0"
                 ::= { enterprises 35450}

leofsGroups OBJECT IDENTIFIER ::= { leofs 1 }
staticOid OBJECT IDENTIFIER   ::= { leofs 56}

-- =====================================
-- Items
-- =====================================
--
-- ErlangVM Related Items
--
node-name
    OBJECT-TYPE
        SYNTAX DisplayString
        MAX-ACCESS read-only
        STATUS current
        DESCRIPTION "Node name"
        ::= { staticOid 1 }

vm-proc-count-1m
    OBJECT-TYPE
        SYNTAX Gauge32
        MAX-ACCESS read-only
        STATUS current
        DESCRIPTION "Num of Processes (1min mean)"
        ::= { staticOid 2 }

vm-total-mem-1m
    OBJECT-TYPE
        SYNTAX Gauge32
        MAX-ACCESS read-only
        STATUS current
        DESCRIPTION "Total Memory (1min mean)"
        ::= { staticOid 3 }

vm-system-mem-1m
    OBJECT-TYPE
        SYNTAX Gauge32
        MAX-ACCESS read-only
        STATUS current
        DESCRIPTION "System Memory (1min mean)"
        ::= { staticOid 4 }

vm-procs-mem-1m
    OBJECT-TYPE
        SYNTAX Gauge32
        MAX-ACCESS read-only
        STATUS current
        DESCRIPTION "Procs Memory (1min mean)"
        ::= { staticOid 5 }

vm-ets-mem-1m
    OBJECT-TYPE
        SYNTAX Gauge32
        MAX-ACCESS read-only
        STATUS current
        DESCRIPTION "ETS Memory (1min mean)"
        ::= { staticOid 6 }

vm-proc-count-5m
    OBJECT-TYPE
        SYNTAX Gauge32
        MAX-ACCESS read-only
        STATUS current
        DESCRIPTION "Num of Processes (5min mean)"
        ::= { staticOid 7 }

vm-total-mem-5m
    OBJECT-TYPE
        SYNTAX Gauge32
        MAX-ACCESS read-only
        STATUS current
        DESCRIPTION "Total Memory (5min mean)"
        ::= { staticOid 8 }

vm-system-mem-5m
    OBJECT-TYPE
        SYNTAX Gauge32
        MAX-ACCESS read-only
        STATUS current
        DESCRIPTION "System Memory (5min mean)"
        ::= { staticOid 9 }

vm-procs-mem-5m
    OBJECT-TYPE
        SYNTAX Gauge32
        MAX-ACCESS read-only
        STATUS current
        DESCRIPTION "Procs Memory (5min mean)"
        ::= { staticOid 10 }

vm-ets-mem-5m
    OBJECT-TYPE
        SYNTAX Gauge32
        MAX-ACCESS read-only
        STATUS current
        DESCRIPTION "ETS Memory (5min mean)"
        ::= { staticOid 11 }

--
-- Request-related Items
--
req-writes-1m
    OBJECT-TYPE
        SYNTAX Gauge32
        MAX-ACCESS read-only
        STATUS current
        DESCRIPTION "Total of Writes during 1min"
        ::= { staticOid 12 }

req-reads-1m
    OBJECT-TYPE
        SYNTAX Gauge32
        MAX-ACCESS read-only
        STATUS current
        DESCRIPTION "Total of Reads during 1min"
        ::= { staticOid 13 }

req-deletes-1m
    OBJECT-TYPE
        SYNTAX Gauge32
        MAX-ACCESS read-only
        STATUS current
        DESCRIPTION "Total of Deletes during 1min"
        ::= { staticOid 14 }

req-writes-5m
    OBJECT-TYPE
        SYNTAX Gauge32
        MAX-ACCESS read-only
        STATUS current
        DESCRIPTION "Total of Writes during 5min"
        ::= { staticOid 15 }

req-reads-5m
    OBJECT-TYPE
        SYNTAX Gauge32
        MAX-ACCESS read-only
        STATUS current
        DESCRIPTION "Total of Reads during 5min"
        ::= { staticOid 16 }

req-deletes-5m
    OBJECT-TYPE
        SYNTAX Gauge32
        MAX-ACCESS read-only
        STATUS current
        DESCRIPTION "Total of Deletes during 5min"
        ::= { staticOid 17 }

--
-- Object Store related Items
--
storage-active-objects
    OBJECT-TYPE
        SYNTAX Gauge32
        MAX-ACCESS read-only
        STATUS current
        DESCRIPTION "Active Objects during"
        ::= { staticOid 18 }

storage-total-objects
    OBJECT-TYPE
        SYNTAX Gauge32
        MAX-ACCESS read-only
        STATUS current
        DESCRIPTION "Total Objects during"
        ::= { staticOid 19 }

storage-active-objects-sizes
    OBJECT-TYPE
        SYNTAX Gauge32
        MAX-ACCESS read-only
        STATUS current
        DESCRIPTION "Active Objects Sizes during"
        ::= { staticOid 20 }

storage-total-objects-sizes
    OBJECT-TYPE
        SYNTAX Gauge32
        MAX-ACCESS read-only
        STATUS current
        DESCRIPTION "Total Objects Sizes during"
        ::= { staticOid 21 }

--
-- MQ-related items
--
mq-num-of-msg-replication
    OBJECT-TYPE
        SYNTAX Gauge32
        MAX-ACCESS read-only
        STATUS current
        DESCRIPTION "Total number of messages of replication"
        ::= { staticOid 22 }

mq-num-of-msg-sync-vnode
    OBJECT-TYPE
        SYNTAX Gauge32
        MAX-ACCESS read-only
        STATUS current
        DESCRIPTION "Total number of messages of sync vnode"
        ::= { staticOid 23 }

mq-num-of-msg-rebalance
    OBJECT-TYPE
        SYNTAX Gauge32
        MAX-ACCESS read-only
        STATUS current
        DESCRIPTION "Total number of messages of rebalance"
        ::= { staticOid 24 }

---
--- Optional VM-related items
---
vm-used-per-allocated-mem-1m
    OBJECT-TYPE
        SYNTAX Gauge32
        MAX-ACCESS read-only
        STATUS current
        DESCRIPTION "Used per allocated memory ratio (1min mean)"
        ::= { staticOid 31 }

vm-allocated-mem-1m
    OBJECT-TYPE
        SYNTAX Gauge32
        MAX-ACCESS read-only
        STATUS current
        DESCRIPTION "Allocated memory (1min mean)"
        ::= { staticOid 32 }

vm-used-per-allocated-mem-5m
    OBJECT-TYPE
        SYNTAX Gauge32
        MAX-ACCESS read-only
        STATUS current
        DESCRIPTION "Used per allocated memory ratio (5min mean)"
        ::= { staticOid 33 }

vm-allocated-mem-5m
    OBJECT-TYPE
        SYNTAX Gauge32
        MAX-ACCESS read-only
        STATUS current
        DESCRIPTION "Allocated memory (5min mean)"
            ::= { staticOid 34 }

---
--- Other MQ related items
--- @since 2018-03-22 (v1.4.0)
---
mq-num-of-msg-recovery-node
    OBJECT-TYPE
        SYNTAX Gauge32
        MAX-ACCESS read-only
        STATUS current
        DESCRIPTION "Total number of messages of recovery node"
        ::= { staticOid 41 }

mq-num-of-msg-deletion-dir
    OBJECT-TYPE
        SYNTAX Gauge32
        MAX-ACCESS read-only
        STATUS current
        DESCRIPTION "Total number of messages of deletion directories"
        ::= { staticOid 42 }

mq-num-of-msg-async-deletion-dir
    OBJECT-TYPE
        SYNTAX Gauge32
        MAX-ACCESS read-only
        STATUS current
        DESCRIPTION "Total number of messages of async deletion directories"
        ::= { staticOid 43 }

mq-num-of-msg-req-deletion-dir
    OBJECT-TYPE
        SYNTAX Gauge32
        MAX-ACCESS read-only
        STATUS current
        DESCRIPTION "Total number of messages of request of deletion directories"
        ::= { staticOid 44 }

mq-mdcr-num-of-msg-req-comp-metadata
    OBJECT-TYPE
        SYNTAX Gauge32
        MAX-ACCESS read-only
        STATUS current
        DESCRIPTION "Total number of messages of comparison metadata between data centers"
        ::= { staticOid 45 }

mq-mdcr-num-of-msg-req-sync-obj
    OBJECT-TYPE
        SYNTAX Gauge32
        MAX-ACCESS read-only
        STATUS current
        DESCRIPTION "Total number of messages of sync objects between data centers"
            ::= { staticOid 46 }

---
--- Data-compaction related items
--- @since 2018-03-22 (v1.4.0)
---
comp-state
    OBJECT-TYPE
        SYNTAX Gauge32
        MAX-ACCESS read-only
        STATUS current
        DESCRIPTION "Current state of data-compaction"
            ::= { staticOid 51 }

comp-last-start-datetime
    OBJECT-TYPE
        SYNTAX Gauge32
        MAX-ACCESS read-only
        STATUS current
        DESCRIPTION "Last start date time"
            ::= { staticOid 52 }

comp-last-end-datetime
    OBJECT-TYPE
        SYNTAX Gauge32
        MAX-ACCESS read-only
        STATUS current
        DESCRIPTION "Last end date time"
            ::= { staticOid 53 }

comp-num-of-pending-targets
    OBJECT-TYPE
        SYNTAX Gauge32
        MAX-ACCESS read-only
        STATUS current
        DESCRIPTION "Total number of pending targets of data compaction"
            ::= { staticOid 54 }

comp-num-of-ongoing-targets
    OBJECT-TYPE
        SYNTAX Gauge32
        MAX-ACCESS read-only
        STATUS current
        DESCRIPTION "Total number of ongoing targets of data compaction"
            ::= { staticOid 55 }

comp-num-of-out-of-targets
    OBJECT-TYPE
        SYNTAX Gauge32
        MAX-ACCESS read-only
        STATUS current
        DESCRIPTION "Total number of out of targets of data compaction"
            ::= { staticOid 56 }

--
-- Global Group
--
leofsGroup OBJECT-GROUP
        OBJECTS {node-name,
                 vm-proc-count-1m, vm-total-mem-1m, vm-system-mem-1m, vm-procs-mem-1m, vm-ets-mem-1m,
                 vm-proc-count-5m, vm-total-mem-5m, vm-system-mem-5m, vm-procs-mem-5m, vm-ets-mem-5m,
                 req-writes-1m, req-reads-1m, req-deletes-1m,
                 req-writes-5m, req-reads-5m, req-deletes-5m,
                 storage-active-objects, storage-total-objects, storage-active-objects-sizes, storage-total-objects-sizes,
                 mq-num-of-msg-replication, mq-num-of-msg-sync-vnode, mq-num-of-msg-rebalance,
                 vm-used-per-allocated-mem-1m, vm-allocated-mem-1m,
                 vm-used-per-allocated-mem-5m, vm-allocated-mem-5m,
                 mq-num-of-msg-recovery-node, mq-num-of-msg-deletion-dir,
                 mq-num-of-msg-async-deletion-dir, mq-num-of-msg-req-deletion-dir,
                 mq-mdcr-num-of-msg-req-comp-metadata, mq-mdcr-num-of-msg-req-sync-obj,
                 comp-state, comp-last-start-datetime, comp-last-end-datetime,
                 comp-num-of-pending-targets, comp-num-of-ongoing-targets, comp-num-of-out-of-targets
        }
        STATUS current
        DESCRIPTION "leofs group"
        ::= { leofsGroups 1 }

END
